# Test of sizes, for bearings and bolts.

from FreeCAD import Base
import Mesh
import Part

import math

import polarMesh

numDivs = 120

# radius of wheel, overall
r1 = 74.999

# half of inside distance between planes
g = (0.6 * 25.4) / 2

# that, plus the width of the spokes
h = g + 2.5

# not sure plain h will be used
h1 = h + 2

# base width for structural elements
w = 2.01

# A cylinder, centered along the z-axis.
def zCylinder(r, z0, z1):
	a = Part.makeCylinder(r, z1-z0)
	a.translate(Base.Vector(0,0,z0))
	return a

# A ring, centered around the z-axis.
def ring(r0, r1, z0, z1):
	a = zCylinder(r1, z0, z1)
	a = a.cut(zCylinder(r0, z0, z1))
	return a

# A "spoke".
def spoke(r0, r1, z0, z1, w, th):
	a = Part.makeBox(r1-r0, w, z1-z0)
	a.translate(Base.Vector(r0, -w/2.0, z0))
	a.rotate(Base.Vector(0,0,0), Base.Vector(0,0,1),
		th * (180 / math.pi))
	return a

# A cylinder, located using polar coordinates.
# Suitable for "drilling" (using subtraction)
# Args:
#	radius - radius of cylinder
#	r, th - polar coordinates of hole (along z-axis)
#	z0, z1 - z coordinates of cylinder
# Returns: a, with a hole cut in it
def offsetCylinder(radius, r, th, z0, z1):
	c = Part.makeCylinder(radius, z1-z0)
 	c.translate(Base.Vector(r*math.cos(th), r*math.sin(th),z0))
	return c

# Function defining how radius changes with angle.
def f(th):
	r0a = 22
	r1a = r1 - 14   # outer ending radius is a bit smaller
	a = (th / (2 * math.pi))
	return r0a + (r1a - r0a) * a

# hub, with space for bearings
a = ring(10, 14, -h1, h1)
# adding a tiny bit to these
a = a.cut(zCylinder(11.025, -h1, -(h1-9)))
a = a.cut(zCylinder(11.05, h1-9, h1))

# mounting holes
r2 = 22.1
for i in xrange(0, 1):
	th = 2 * math.pi * (2*i+1) / 10.0
#	a = a.fuse(offsetCylinder(9.9, r2, th, -(h+7), -g))
#	a = a.cut(offsetCylinder(4, r2, th, -(h+7), -(g-5)))
#	a = a.cut(offsetCylinder(8, r2, th, -(g+4), -(g-5)))
	# only showing the + side hole (so as to distinguish
	# sides, since bearing holes are different sizes)
	a = a.fuse(offsetCylinder(9.9, r2, th, g, h+7))
	# also making mounting hole slightly bigger
	a = a.cut(offsetCylinder(4.05, r2, th, g-5, h+7))
	a = a.cut(offsetCylinder(8, r2, th, g-5, g+4))

Part.show(a)
